-- Handwritten file that contains common structures from NGAP, E1AP and F1AP
Criticality ::= ENUMERATED { reject, ignore, notify }

TransportLayerAddress ::= BIT STRING (SIZE (1..160, ...))
GTP-TEID ::= OCTET STRING (SIZE (4))
GTPTunnel ::= SEQUENCE {
	transportLayerAddress		TransportLayerAddress,
	gTP-TEID					GTP-TEID,
	iE-Extensions		ProtocolExtensionContainer { {GTPTunnel-ExtIEs } } OPTIONAL,
	...
}

GTPTunnel-ExtIEs NGAP-PROTOCOL-EXTENSION ::= {
	...
}

-- E1 PDU-Session-ID / F1 PDUSessionID / NG PDUSessionID / RRC PDU-SessionID
PDU-Session-ID ::= INTEGER (0..255)
