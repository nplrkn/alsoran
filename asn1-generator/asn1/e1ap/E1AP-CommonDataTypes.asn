-- ASN1START
-- **************************************************************
--
-- Common definitions
--
-- **************************************************************

E1AP-CommonDataTypes {
itu-t (0) identified-organization (4) etsi (0) mobileDomain (0)
ngran-access (22) modules (3) e1ap (5) version1 (1) e1ap-CommonDataTypes (3) }

DEFINITIONS AUTOMATIC TAGS ::= 

BEGIN

-- **************************************************************
--
-- Extension constants
--
-- **************************************************************

maxPrivateIEs 									INTEGER ::= 65535
maxProtocolExtensions 							INTEGER ::= 65535
maxProtocolIEs									INTEGER ::= 65535

-- **************************************************************
--
-- Common Data Types
--
-- **************************************************************

Criticality ::= ENUMERATED { reject, ignore, notify }

Presence ::= ENUMERATED { optional, conditional, mandatory }

PrivateIE-ID ::= CHOICE {
	local				INTEGER (0.. maxPrivateIEs),
	global			OBJECT IDENTIFIER
}

ProcedureCode ::= INTEGER (0..255)

ProtocolExtensionID ::= INTEGER (0..maxProtocolExtensions)

ProtocolIE-ID ::= INTEGER (0..maxProtocolIEs)

TriggeringMessage ::= ENUMERATED { initiating-message, successful-outcome, unsuccessful-outcome }

END
-- ASN1STOP
