-- ASN1START 
-- **************************************************************
--
-- Constant definitions
--
-- **************************************************************

F1AP-Constants { 
itu-t (0) identified-organization (4) etsi (0) mobileDomain (0) 
ngran-access (22) modules (3) f1ap (3) version1 (1) f1ap-Constants (4) } 

DEFINITIONS AUTOMATIC TAGS ::= 

BEGIN

-- **************************************************************
--
-- IE parameter types from other modules.
--
-- **************************************************************

IMPORTS
	ProcedureCode,
	ProtocolIE-ID

FROM F1AP-CommonDataTypes;


-- **************************************************************
--
-- Elementary Procedures
--
-- **************************************************************

id-Reset									ProcedureCode ::= 0
id-F1Setup									ProcedureCode ::= 1
id-ErrorIndication							ProcedureCode ::= 2
id-gNBDUConfigurationUpdate					ProcedureCode ::= 3
id-gNBCUConfigurationUpdate					ProcedureCode ::= 4
id-UEContextSetup							ProcedureCode ::= 5
id-UEContextRelease							ProcedureCode ::= 6
id-UEContextModification					ProcedureCode ::= 7
id-UEContextModificationRequired			ProcedureCode ::= 8
id-procedure-code-9-not-to-be-used			ProcedureCode ::= 9
id-UEContextReleaseRequest					ProcedureCode ::= 10
id-InitialULRRCMessageTransfer				ProcedureCode ::= 11
id-DLRRCMessageTransfer						ProcedureCode ::= 12
id-ULRRCMessageTransfer						ProcedureCode ::= 13
id-privateMessage							ProcedureCode ::= 14
id-UEInactivityNotification					ProcedureCode ::= 15
id-GNBDUResourceCoordination				ProcedureCode ::= 16
id-SystemInformationDeliveryCommand			ProcedureCode ::= 17
id-Paging									ProcedureCode ::= 18
id-Notify									ProcedureCode ::= 19
id-WriteReplaceWarning						ProcedureCode ::= 20
id-PWSCancel								ProcedureCode ::= 21
id-PWSRestartIndication						ProcedureCode ::= 22
id-PWSFailureIndication						ProcedureCode ::= 23
id-GNBDUStatusIndication 					ProcedureCode ::= 24
id-RRCDeliveryReport		 				ProcedureCode ::= 25
id-F1Removal								ProcedureCode ::= 26
id-NetworkAccessRateReduction				ProcedureCode ::= 27
id-TraceStart								ProcedureCode ::= 28
id-DeactivateTrace							ProcedureCode ::= 29
id-DUCURadioInformationTransfer				ProcedureCode ::= 30
id-CUDURadioInformationTransfer				ProcedureCode ::= 31
id-BAPMappingConfiguration					ProcedureCode ::= 32
id-GNBDUResourceConfiguration				ProcedureCode ::= 33
id-IABTNLAddressAllocation					ProcedureCode ::= 34
id-IABUPConfigurationUpdate					ProcedureCode ::= 35
id-resourceStatusReportingInitiation		ProcedureCode ::= 36
id-resourceStatusReporting					ProcedureCode ::= 37
id-accessAndMobilityIndication				ProcedureCode ::= 38
id-accessSuccess							ProcedureCode ::= 39
id-cellTrafficTrace 						ProcedureCode ::= 40 
id-PositioningMeasurementExchange			ProcedureCode ::= 41
id-PositioningAssistanceInformationControl	ProcedureCode ::= 42
id-PositioningAssistanceInformationFeedback	ProcedureCode ::= 43
id-PositioningMeasurementReport				ProcedureCode ::= 44
id-PositioningMeasurementAbort				ProcedureCode ::= 45
id-PositioningMeasurementFailureIndication	ProcedureCode ::= 46
id-PositioningMeasurementUpdate				ProcedureCode ::= 47
id-TRPInformationExchange					ProcedureCode ::= 48
id-PositioningInformationExchange			ProcedureCode ::= 49
id-PositioningActivation					ProcedureCode ::= 50
id-PositioningDeactivation					ProcedureCode ::= 51
id-E-CIDMeasurementInitiation				ProcedureCode ::= 52
id-E-CIDMeasurementFailureIndication		ProcedureCode ::= 53
id-E-CIDMeasurementReport					ProcedureCode ::= 54
id-E-CIDMeasurementTermination				ProcedureCode ::= 55
id-PositioningInformationUpdate				ProcedureCode ::= 56
id-ReferenceTimeInformationReport			ProcedureCode ::= 57
id-ReferenceTimeInformationReportingControl	ProcedureCode ::= 58
id-BroadcastContextSetup					ProcedureCode ::= 59
id-BroadcastContextRelease					ProcedureCode ::= 60
id-BroadcastContextReleaseRequest			ProcedureCode ::= 61
id-BroadcastContextModification				ProcedureCode ::= 62
id-MulticastGroupPaging						ProcedureCode ::= 63
id-MulticastContextSetup					ProcedureCode ::= 64
id-MulticastContextRelease					ProcedureCode ::= 65
id-MulticastContextReleaseRequest			ProcedureCode ::= 66
id-MulticastContextModification				ProcedureCode ::= 67
id-MulticastDistributionSetup				ProcedureCode ::= 68
id-MulticastDistributionRelease				ProcedureCode ::= 69
id-PDCMeasurementInitiation					ProcedureCode ::= 70
id-PDCMeasurementReport						ProcedureCode ::= 71
id-procedure-code-72-not-to-be-used			ProcedureCode ::= 72
id-procedure-code-73-not-to-be-used			ProcedureCode ::= 73
id-procedure-code-74-not-to-be-used			ProcedureCode ::= 74
id-pRSConfigurationExchange					ProcedureCode ::= 75
id-measurementPreconfiguration				ProcedureCode ::= 76
id-measurementActivation					ProcedureCode ::= 77
id-QoEInformationTransfer					ProcedureCode ::= 78
id-PDCMeasurementTerminationCommand			ProcedureCode ::= 79
id-PDCMeasurementFailureIndication 			ProcedureCode ::= 80
id-PosSystemInformationDeliveryCommand		ProcedureCode ::= 81
id-DUCUCellSwitchNotification				ProcedureCode ::= 82
id-CUDUCellSwitchNotification				ProcedureCode ::= 83
id-DUCUTAInformationTransfer				ProcedureCode ::= 84
id-CUDUTAInformationTransfer				ProcedureCode ::= 85
id-QoEInformationTransferControl			ProcedureCode ::= 86 
id-RachIndication							ProcedureCode ::= 87
id-TimingSynchronisationStatus				ProcedureCode ::= 88
id-TimingSynchronisationStatusReport		ProcedureCode ::= 89
id-MIABF1SetupTriggering					ProcedureCode ::= 90
id-MIABF1SetupOutcomeNotification			ProcedureCode ::= 91
id-MulticastContextNotification 			ProcedureCode ::= 92
id-MulticastCommonConfiguration				ProcedureCode ::= 93
id-BroadcastTransportResourceRequest		ProcedureCode ::= 94
id-DUCUAccessAndMobilityIndication			ProcedureCode ::= 95
id-SRSInformationReservationNotification	ProcedureCode ::= 96




-- **************************************************************
--
-- Extension constants
--
-- **************************************************************

maxPrivateIEs							INTEGER ::= 65535
maxProtocolExtensions					INTEGER ::= 65535
maxProtocolIEs							INTEGER ::= 65535
-- **************************************************************
--
-- Lists
--
-- **************************************************************

maxNRARFCN								INTEGER ::= 3279165
maxnoofErrors							INTEGER ::= 256
maxnoofIndividualF1ConnectionsToReset	INTEGER ::= 65536
maxCellingNBDU							INTEGER ::= 512
maxnoofSCells							INTEGER ::= 32
maxnoofSRBs								INTEGER ::= 8
maxnoofDRBs								INTEGER ::= 64
maxnoofULUPTNLInformation				INTEGER ::= 2
maxnoofDLUPTNLInformation				INTEGER ::= 2
maxnoofBPLMNs							INTEGER ::= 6
maxnoofCandidateSpCells					INTEGER ::= 64
maxnoofPotentialSpCells					INTEGER ::= 64
maxnoofNrCellBands						INTEGER ::= 32
maxnoofSIBTypes							INTEGER ::= 32
maxnoofSITypes							INTEGER ::= 32
maxnoofPagingCells						INTEGER ::= 512
maxnoofTNLAssociations					INTEGER ::= 32
maxnoofQoSFlows							INTEGER ::= 64
maxnoofSliceItems						INTEGER ::= 1024
maxCellineNB							INTEGER ::= 256
maxnoofExtendedBPLMNs					INTEGER ::= 6
maxnoofUEIDs							INTEGER ::= 65536
maxnoofBPLMNsNR							INTEGER ::= 12
maxnoofUACPLMNs							INTEGER ::= 12
maxnoofUACperPLMN						INTEGER ::= 64
maxnoofAdditionalSIBs					INTEGER ::= 63
maxnoofslots							INTEGER ::= 5120
maxnoofTLAs								INTEGER ::=	16
maxnoofGTPTLAs							INTEGER ::=	16
maxnoofBHRLCChannels					INTEGER ::= 65536
maxnoofRoutingEntries					INTEGER ::= 1024
maxnoofIABSTCInfo						INTEGER ::= 45
maxnoofSymbols							INTEGER ::= 14
maxnoofServingCells						INTEGER ::= 32
maxnoofDUFSlots							INTEGER ::= 320
maxnoofHSNASlots						INTEGER ::= 5120
maxnoofServedCellsIAB					INTEGER ::= 512
maxnoofSSBarea							INTEGER ::=64
maxnoofChildIABNodes					INTEGER ::= 1024
maxnoofNonUPTrafficMappings				INTEGER ::= 32
maxnoofTLAsIAB							INTEGER ::= 1024
maxnoofMappingEntries					INTEGER ::= 67108864
maxnoofDSInfo							INTEGER ::= 64
maxnoofEgressLinks						INTEGER ::= 2
maxnoofULUPTNLInformationforIAB			INTEGER ::= 32678
maxnoofUPTNLAddresses					INTEGER ::= 8
maxnoofSLDRBs							INTEGER ::= 512
maxnoofQoSParaSets						INTEGER ::= 8
maxnoofPC5QoSFlows						INTEGER ::= 2048
maxnoofSSBAreas							INTEGER ::=	64
maxnoofPhysicalResourceBlocks			INTEGER ::= 275
maxnoofPhysicalResourceBlocks-1			INTEGER ::= 274
maxnoofPRACHconfigs						INTEGER ::= 16
maxnoofRAReports						INTEGER ::= 64
maxnoofRLFReports						INTEGER ::= 64
maxnoofAdditionalPDCPDuplicationTNL		INTEGER ::=	2
maxnoofRLCDuplicationState				INTEGER ::=	3
maxnoofCHOcells							INTEGER ::= 8
maxnoofMDTPLMNs							INTEGER ::=	16
maxnoofCAGsupported						INTEGER ::= 12
maxnoofNIDsupported						INTEGER ::= 12
maxnoofNRSCSs							INTEGER ::= 5
maxnoofExtSliceItems					INTEGER ::= 65535 
maxnoofPosMeas							INTEGER ::=	16384
maxnoofTRPInfoTypes						INTEGER ::=	64 
maxnoofTRPs								INTEGER ::=	65535 
maxnoofSRSTriggerStates					INTEGER ::= 3
maxnoofSpatialRelations					INTEGER ::= 64
maxnoBcastCell							INTEGER ::= 16384
maxnoofAngleInfo						INTEGER ::= 65535
maxnooflcs-gcs-translation				INTEGER ::= 3
maxnoofPath								INTEGER ::= 2
maxnoofMeasE-CID						INTEGER ::= 64
maxnoofSSBs								INTEGER ::= 255
maxnoSRS-ResourceSets					INTEGER ::= 16
maxnoSRS-ResourcePerSet					INTEGER ::= 16
maxnoSRS-Carriers						INTEGER ::= 32
maxnoSCSs								INTEGER ::= 5
maxnoSRS-Resources						INTEGER ::= 64
maxnoSRS-PosResources					INTEGER ::= 64
maxnoSRS-PosResourceSets				INTEGER ::= 16
maxnoSRS-PosResourcePerSet				INTEGER ::= 16
maxnoofPRS-ResourceSets					INTEGER ::= 2
maxnoofPRS-ResourcesPerSet				INTEGER ::= 64
maxNoOfMeasTRPs							INTEGER ::= 64
maxnoofPRSresourceSets					INTEGER ::= 8
maxnoofPRSresources						INTEGER ::= 64
maxnoofSuccessfulHOReports				INTEGER ::= 64
maxnoofNR-UChannelIDs					INTEGER ::= 16
maxServedCellforSON						INTEGER ::= 256
maxNeighbourCellforSON					INTEGER ::= 32
maxAffectedCells						INTEGER ::= 32
maxnoofMRBs								INTEGER ::= 32
maxnoofMBSQoSFlows						INTEGER ::= 64
maxnoofMBSFSAs 							INTEGER ::= 256
maxnoofUEIDforPaging 					INTEGER ::= 4096
maxnoofCellsforMBS						INTEGER ::= 512
maxnoofTAIforMBS						INTEGER ::= 512
maxnoofMBSAreaSessionIDs				INTEGER ::= 256
maxnoofMBSServiceAreaInformation		INTEGER ::= 256
maxnoofIABCongInd						INTEGER ::= 1024
maxnoofNeighbourNodeCellsIAB			INTEGER ::= 1024 
maxnoofRBsetsPerCell					INTEGER ::= 8
maxnoofRBsetsPerCell-1					INTEGER ::= 7
maxnoofMeasPDC							INTEGER ::= 16
maxnoARPs								INTEGER ::=	16
maxnoofULAoAs							INTEGER ::= 8
maxNoPathExtended						INTEGER ::= 8
maxnoTRPTEGs							INTEGER ::= 8
maxFreqLayers							INTEGER ::= 4
maxNumResourcesPerAngle					INTEGER ::= 24
maxnoAzimuthAngles						INTEGER ::= 3600
maxnoElevationAngles					INTEGER ::= 1801
maxnoofPRSTRPs							INTEGER ::= 256
maxnoofQoEInformation					INTEGER ::= 16
maxnoofUuRLCChannels					INTEGER ::= 32
maxnoofPC5RLCChannels					INTEGER ::= 512
maxnoofSMBRValues						INTEGER ::= 8
maxnoofMRBsforUE						INTEGER ::= 64
maxnoofMBSSessionsofUE					INTEGER ::= 256
maxnoofSLdestinations					INTEGER ::= 32
maxnoofNSAGs							INTEGER ::= 256
maxnoofSDTBearers						INTEGER ::= 72
maxnoofServingCellMOs					INTEGER ::= 16
maxNrofBWPs								INTEGER ::= 8
maxnoofPosSITypes						INTEGER ::= 32
maxnoofUETypes							INTEGER ::= 8
maxnoofLTMCells							INTEGER	::= 8
maxnoofTAList							INTEGER	::= 8
maxnoofLTMgNB-DUs						INTEGER	::= 8
maxnoofUEsInQMCTransferControlMessage	INTEGER ::= 512
maxnoofUEsforRAReportIndications		INTEGER ::= 64
maxnoofSuccessfulPSCellChangeReports	INTEGER ::= 64
maxnoofPeriodicities					INTEGER ::= 8
maxnoofThresholdMBS-1					INTEGER ::= 7
maxMBSSessionsinSessionInfoList			INTEGER ::= 1024
maxnoofLBTFailureInformation			INTEGER ::= 64
maxnoofRSPPQoSFlows						INTEGER ::= 2048
maxnoVACell								INTEGER ::= 32
maxnoAggregatedSRS-Resources			INTEGER ::= 3
maxnoAggregatedPosSRSResourceSets		INTEGER ::= 3
maxnoAggregatedPosPRSResourceSets		INTEGER ::= 3
maxnoofTimeWindowSRS					INTEGER ::= 16
maxnoofTimeWindowMea					INTEGER ::= 16
maxnoPreconfiguredSRS					INTEGER ::= 16
maxnoHopsMinusOne						INTEGER ::= 5
maxnoAggCombinations					INTEGER ::= 2
maxnoAggregatedPosSRSCombinations		INTEGER ::= 32







-- **************************************************************
--
-- IEs
--
-- **************************************************************

id-Cause											ProtocolIE-ID ::= 0
id-Cells-Failed-to-be-Activated-List				ProtocolIE-ID ::= 1
id-Cells-Failed-to-be-Activated-List-Item			ProtocolIE-ID ::= 2
id-Cells-to-be-Activated-List						ProtocolIE-ID ::= 3
id-Cells-to-be-Activated-List-Item					ProtocolIE-ID ::= 4
id-Cells-to-be-Deactivated-List						ProtocolIE-ID ::= 5
id-Cells-to-be-Deactivated-List-Item				ProtocolIE-ID ::= 6
id-CriticalityDiagnostics							ProtocolIE-ID ::= 7
id-CUtoDURRCInformation								ProtocolIE-ID ::= 9
id-DRBs-FailedToBeModified-Item						ProtocolIE-ID ::= 12
id-DRBs-FailedToBeModified-List						ProtocolIE-ID ::= 13
id-DRBs-FailedToBeSetup-Item						ProtocolIE-ID ::= 14
id-DRBs-FailedToBeSetup-List						ProtocolIE-ID ::= 15
id-DRBs-FailedToBeSetupMod-Item						ProtocolIE-ID ::= 16
id-DRBs-FailedToBeSetupMod-List						ProtocolIE-ID ::= 17
id-DRBs-ModifiedConf-Item							ProtocolIE-ID ::= 18
id-DRBs-ModifiedConf-List							ProtocolIE-ID ::= 19
id-DRBs-Modified-Item								ProtocolIE-ID ::= 20
id-DRBs-Modified-List								ProtocolIE-ID ::= 21
id-DRBs-Required-ToBeModified-Item					ProtocolIE-ID ::= 22
id-DRBs-Required-ToBeModified-List					ProtocolIE-ID ::= 23
id-DRBs-Required-ToBeReleased-Item					ProtocolIE-ID ::= 24
id-DRBs-Required-ToBeReleased-List					ProtocolIE-ID ::= 25
id-DRBs-Setup-Item									ProtocolIE-ID ::= 26
id-DRBs-Setup-List									ProtocolIE-ID ::= 27
id-DRBs-SetupMod-Item								ProtocolIE-ID ::= 28
id-DRBs-SetupMod-List								ProtocolIE-ID ::= 29
id-DRBs-ToBeModified-Item							ProtocolIE-ID ::= 30
id-DRBs-ToBeModified-List							ProtocolIE-ID ::= 31
id-DRBs-ToBeReleased-Item							ProtocolIE-ID ::= 32
id-DRBs-ToBeReleased-List							ProtocolIE-ID ::= 33
id-DRBs-ToBeSetup-Item								ProtocolIE-ID ::= 34
id-DRBs-ToBeSetup-List								ProtocolIE-ID ::= 35
id-DRBs-ToBeSetupMod-Item							ProtocolIE-ID ::= 36
id-DRBs-ToBeSetupMod-List							ProtocolIE-ID ::= 37
id-DRXCycle											ProtocolIE-ID ::= 38
id-DUtoCURRCInformation								ProtocolIE-ID ::= 39
id-gNB-CU-UE-F1AP-ID								ProtocolIE-ID ::= 40
id-gNB-DU-UE-F1AP-ID								ProtocolIE-ID ::= 41
id-gNB-DU-ID										ProtocolIE-ID ::= 42
id-GNB-DU-Served-Cells-Item							ProtocolIE-ID ::= 43
id-gNB-DU-Served-Cells-List							ProtocolIE-ID ::= 44
id-gNB-DU-Name										ProtocolIE-ID ::= 45
id-ProtocolIE-ID-46-not-to-be-used					ProtocolIE-ID ::= 46
id-oldgNB-DU-UE-F1AP-ID								ProtocolIE-ID ::= 47
id-ResetType										ProtocolIE-ID ::= 48
id-ResourceCoordinationTransferContainer			ProtocolIE-ID ::= 49
id-RRCContainer										ProtocolIE-ID ::= 50
id-SCell-ToBeRemoved-Item							ProtocolIE-ID ::= 51
id-SCell-ToBeRemoved-List							ProtocolIE-ID ::= 52
id-SCell-ToBeSetup-Item								ProtocolIE-ID ::= 53
id-SCell-ToBeSetup-List								ProtocolIE-ID ::= 54
id-SCell-ToBeSetupMod-Item							ProtocolIE-ID ::= 55
id-SCell-ToBeSetupMod-List							ProtocolIE-ID ::= 56
id-Served-Cells-To-Add-Item							ProtocolIE-ID ::= 57
id-Served-Cells-To-Add-List							ProtocolIE-ID ::= 58
id-Served-Cells-To-Delete-Item						ProtocolIE-ID ::= 59
id-Served-Cells-To-Delete-List						ProtocolIE-ID ::= 60
id-Served-Cells-To-Modify-Item						ProtocolIE-ID ::= 61
id-Served-Cells-To-Modify-List						ProtocolIE-ID ::= 62
id-SpCell-ID										ProtocolIE-ID ::= 63
id-SRBID											ProtocolIE-ID ::= 64
id-SRBs-FailedToBeSetup-Item						ProtocolIE-ID ::= 65
id-SRBs-FailedToBeSetup-List						ProtocolIE-ID ::= 66
id-SRBs-FailedToBeSetupMod-Item						ProtocolIE-ID ::= 67
id-SRBs-FailedToBeSetupMod-List						ProtocolIE-ID ::= 68
id-SRBs-Required-ToBeReleased-Item					ProtocolIE-ID ::= 69
id-SRBs-Required-ToBeReleased-List					ProtocolIE-ID ::= 70
id-SRBs-ToBeReleased-Item							ProtocolIE-ID ::= 71
id-SRBs-ToBeReleased-List							ProtocolIE-ID ::= 72
id-SRBs-ToBeSetup-Item								ProtocolIE-ID ::= 73
id-SRBs-ToBeSetup-List								ProtocolIE-ID ::= 74
id-SRBs-ToBeSetupMod-Item							ProtocolIE-ID ::= 75
id-SRBs-ToBeSetupMod-List							ProtocolIE-ID ::= 76
id-TimeToWait										ProtocolIE-ID ::= 77
id-TransactionID									ProtocolIE-ID ::= 78
id-TransmissionActionIndicator						ProtocolIE-ID ::= 79
id-UE-associatedLogicalF1-ConnectionItem 			ProtocolIE-ID ::= 80
id-UE-associatedLogicalF1-ConnectionListResAck		ProtocolIE-ID ::= 81
id-gNB-CU-Name										ProtocolIE-ID ::= 82
id-SCell-FailedtoSetup-List							ProtocolIE-ID ::= 83
id-SCell-FailedtoSetup-Item							ProtocolIE-ID ::= 84
id-SCell-FailedtoSetupMod-List						ProtocolIE-ID ::= 85
id-SCell-FailedtoSetupMod-Item						ProtocolIE-ID ::= 86
id-RRCReconfigurationCompleteIndicator 				ProtocolIE-ID ::= 87
id-Cells-Status-Item								ProtocolIE-ID ::= 88
id-Cells-Status-List								ProtocolIE-ID ::= 89
id-Candidate-SpCell-List							ProtocolIE-ID ::= 90
id-Candidate-SpCell-Item							ProtocolIE-ID ::= 91
id-Potential-SpCell-List							ProtocolIE-ID ::= 92
id-Potential-SpCell-Item							ProtocolIE-ID ::= 93
id-FullConfiguration								ProtocolIE-ID ::= 94
id-C-RNTI											ProtocolIE-ID ::= 95
id-SpCellULConfigured								ProtocolIE-ID ::= 96
id-InactivityMonitoringRequest						ProtocolIE-ID ::= 97
id-InactivityMonitoringResponse						ProtocolIE-ID ::= 98
id-DRB-Activity-Item								ProtocolIE-ID ::= 99
id-DRB-Activity-List								ProtocolIE-ID ::= 100
id-EUTRA-NR-CellResourceCoordinationReq-Container	ProtocolIE-ID ::= 101
id-EUTRA-NR-CellResourceCoordinationReqAck-Container	ProtocolIE-ID ::= 102
id-Protected-EUTRA-Resources-List					ProtocolIE-ID ::= 105
id-RequestType 										ProtocolIE-ID ::= 106
id-ServCellIndex									ProtocolIE-ID ::= 107 
id-RAT-FrequencyPriorityInformation					ProtocolIE-ID ::= 108
id-ExecuteDuplication								ProtocolIE-ID ::= 109
id-NRCGI											ProtocolIE-ID ::= 111
id-PagingCell-Item									ProtocolIE-ID ::= 112
id-PagingCell-List									ProtocolIE-ID ::= 113
id-PagingDRX										ProtocolIE-ID ::= 114
id-PagingPriority 									ProtocolIE-ID ::= 115
id-SItype-List										ProtocolIE-ID ::= 116
id-UEIdentityIndexValue								ProtocolIE-ID ::= 117
id-gNB-CUSystemInformation							ProtocolIE-ID ::= 118
id-HandoverPreparationInformation					ProtocolIE-ID ::= 119
id-GNB-CU-TNL-Association-To-Add-Item				ProtocolIE-ID ::= 120
id-GNB-CU-TNL-Association-To-Add-List				ProtocolIE-ID ::= 121
id-GNB-CU-TNL-Association-To-Remove-Item			ProtocolIE-ID ::= 122
id-GNB-CU-TNL-Association-To-Remove-List			ProtocolIE-ID ::= 123
id-GNB-CU-TNL-Association-To-Update-Item			ProtocolIE-ID ::= 124
id-GNB-CU-TNL-Association-To-Update-List			ProtocolIE-ID ::= 125
id-MaskedIMEISV										ProtocolIE-ID ::= 126
id-PagingIdentity									ProtocolIE-ID ::= 127
id-DUtoCURRCContainer								ProtocolIE-ID ::= 128
id-Cells-to-be-Barred-List							ProtocolIE-ID ::= 129
id-Cells-to-be-Barred-Item							ProtocolIE-ID ::= 130
id-TAISliceSupportList								ProtocolIE-ID ::= 131
id-GNB-CU-TNL-Association-Setup-List				ProtocolIE-ID ::= 132
id-GNB-CU-TNL-Association-Setup-Item				ProtocolIE-ID ::= 133
id-GNB-CU-TNL-Association-Failed-To-Setup-List		ProtocolIE-ID ::= 134
id-GNB-CU-TNL-Association-Failed-To-Setup-Item		ProtocolIE-ID ::= 135
id-DRB-Notify-Item									ProtocolIE-ID ::= 136
id-DRB-Notify-List									ProtocolIE-ID ::= 137
id-ProtocolIE-ID-138-not-to-be-used				ProtocolIE-ID ::= 138
id-RANAC											ProtocolIE-ID ::= 139
id-PWSSystemInformation								ProtocolIE-ID ::= 140
id-RepetitionPeriod									ProtocolIE-ID ::= 141
id-NumberofBroadcastRequest							ProtocolIE-ID ::= 142
id-Cells-To-Be-Broadcast-List						ProtocolIE-ID ::= 144
id-Cells-To-Be-Broadcast-Item						ProtocolIE-ID ::= 145
id-Cells-Broadcast-Completed-List 					ProtocolIE-ID ::= 146
id-Cells-Broadcast-Completed-Item 					ProtocolIE-ID ::= 147
id-Broadcast-To-Be-Cancelled-List 					ProtocolIE-ID ::= 148
id-Broadcast-To-Be-Cancelled-Item 					ProtocolIE-ID ::= 149
id-Cells-Broadcast-Cancelled-List 					ProtocolIE-ID ::= 150
id-Cells-Broadcast-Cancelled-Item 					ProtocolIE-ID ::= 151
id-NR-CGI-List-For-Restart-List 					ProtocolIE-ID ::= 152
id-NR-CGI-List-For-Restart-Item 					ProtocolIE-ID ::= 153
id-PWS-Failed-NR-CGI-List 							ProtocolIE-ID ::= 154
id-PWS-Failed-NR-CGI-Item 							ProtocolIE-ID ::= 155
id-ConfirmedUEID									ProtocolIE-ID ::= 156
id-Cancel-all-Warning-Messages-Indicator			ProtocolIE-ID ::= 157
id-GNB-DU-UE-AMBR-UL								ProtocolIE-ID ::= 158
id-DRXConfigurationIndicator						ProtocolIE-ID ::= 159
id-RLC-Status										ProtocolIE-ID ::= 160
id-DLPDCPSNLength									ProtocolIE-ID ::= 161
id-GNB-DUConfigurationQuery							ProtocolIE-ID ::= 162
id-MeasurementTimingConfiguration					ProtocolIE-ID ::= 163
id-DRB-Information									ProtocolIE-ID ::= 164
id-ServingPLMN										ProtocolIE-ID ::= 165
id-Protected-EUTRA-Resources-Item					ProtocolIE-ID ::= 168
id-GNB-CU-RRC-Version								ProtocolIE-ID ::= 170
id-GNB-DU-RRC-Version								ProtocolIE-ID ::= 171
id-GNBDUOverloadInformation							ProtocolIE-ID ::= 172
id-CellGroupConfig									ProtocolIE-ID ::= 173
id-RLCFailureIndication								ProtocolIE-ID ::= 174
id-UplinkTxDirectCurrentListInformation				ProtocolIE-ID ::= 175
id-DC-Based-Duplication-Configured					ProtocolIE-ID ::= 176
id-DC-Based-Duplication-Activation					ProtocolIE-ID ::= 177
id-SULAccessIndication								ProtocolIE-ID ::= 178
id-AvailablePLMNList								ProtocolIE-ID ::= 179
id-PDUSessionID										ProtocolIE-ID ::= 180
id-ULPDUSessionAggregateMaximumBitRate				ProtocolIE-ID ::= 181
id-ServingCellMO									ProtocolIE-ID ::= 182
id-QoSFlowMappingIndication							ProtocolIE-ID ::= 183
id-RRCDeliveryStatusRequest							ProtocolIE-ID ::= 184
id-RRCDeliveryStatus								ProtocolIE-ID ::= 185
id-BearerTypeChange									ProtocolIE-ID ::= 186
id-RLCMode											ProtocolIE-ID ::= 187
id-Duplication-Activation							ProtocolIE-ID ::= 188
id-Dedicated-SIDelivery-NeededUE-List				ProtocolIE-ID ::= 189
id-Dedicated-SIDelivery-NeededUE-Item				ProtocolIE-ID ::= 190
id-DRX-LongCycleStartOffset							ProtocolIE-ID ::= 191
id-ULPDCPSNLength									ProtocolIE-ID ::= 192
id-SelectedBandCombinationIndex						ProtocolIE-ID ::= 193
id-SelectedFeatureSetEntryIndex						ProtocolIE-ID ::= 194
id-ResourceCoordinationTransferInformation			ProtocolIE-ID ::= 195
id-ExtendedServedPLMNs-List							ProtocolIE-ID ::= 196
id-ExtendedAvailablePLMN-List						ProtocolIE-ID ::= 197
id-Associated-SCell-List							ProtocolIE-ID ::= 198
id-latest-RRC-Version-Enhanced						ProtocolIE-ID ::= 199
id-Associated-SCell-Item							ProtocolIE-ID ::= 200
id-Cell-Direction									ProtocolIE-ID ::= 201
id-SRBs-Setup-List									ProtocolIE-ID ::= 202
id-SRBs-Setup-Item									ProtocolIE-ID ::= 203
id-SRBs-SetupMod-List								ProtocolIE-ID ::= 204
id-SRBs-SetupMod-Item								ProtocolIE-ID ::= 205
id-SRBs-Modified-List								ProtocolIE-ID ::= 206
id-SRBs-Modified-Item								ProtocolIE-ID ::= 207
id-Ph-InfoSCG										ProtocolIE-ID ::= 208
id-RequestedBandCombinationIndex					ProtocolIE-ID ::= 209
id-RequestedFeatureSetEntryIndex					ProtocolIE-ID ::= 210
id-RequestedP-MaxFR2								ProtocolIE-ID ::= 211
id-DRX-Config										ProtocolIE-ID ::= 212
id-IgnoreResourceCoordinationContainer				ProtocolIE-ID ::= 213
id-UEAssistanceInformation							ProtocolIE-ID ::= 214
id-NeedforGap										ProtocolIE-ID ::= 215
id-PagingOrigin										ProtocolIE-ID ::= 216
id-new-gNB-CU-UE-F1AP-ID							ProtocolIE-ID ::= 217
id-RedirectedRRCmessage								ProtocolIE-ID ::= 218
id-new-gNB-DU-UE-F1AP-ID							ProtocolIE-ID ::= 219
id-NotificationInformation							ProtocolIE-ID ::= 220
id-PLMNAssistanceInfoForNetShar						ProtocolIE-ID ::= 221
id-UEContextNotRetrievable							ProtocolIE-ID ::= 222
id-BPLMN-ID-Info-List								ProtocolIE-ID ::= 223
id-SelectedPLMNID									ProtocolIE-ID ::= 224
id-UAC-Assistance-Info								ProtocolIE-ID ::= 225
id-RANUEID											ProtocolIE-ID ::= 226
id-GNB-DU-TNL-Association-To-Remove-Item			ProtocolIE-ID ::= 227
id-GNB-DU-TNL-Association-To-Remove-List			ProtocolIE-ID ::= 228
id-TNLAssociationTransportLayerAddressgNBDU			ProtocolIE-ID ::= 229
id-portNumber										ProtocolIE-ID ::= 230
id-AdditionalSIBMessageList							ProtocolIE-ID ::= 231
id-Cell-Type										ProtocolIE-ID ::= 232
id-IgnorePRACHConfiguration							ProtocolIE-ID ::= 233
id-CG-Config										ProtocolIE-ID ::= 234
id-PDCCH-BlindDetectionSCG							ProtocolIE-ID ::= 235
id-Requested-PDCCH-BlindDetectionSCG				ProtocolIE-ID ::= 236
id-Ph-InfoMCG										ProtocolIE-ID ::= 237
id-MeasGapSharingConfig								ProtocolIE-ID ::= 238
id-systemInformationAreaID							ProtocolIE-ID ::= 239
id-areaScope										ProtocolIE-ID ::= 240
id-RRCContainer-RRCSetupComplete					ProtocolIE-ID ::= 241
id-TraceActivation									ProtocolIE-ID ::= 242
id-TraceID											ProtocolIE-ID ::= 243
id-Neighbour-Cell-Information-List					ProtocolIE-ID ::= 244
id-ProtocolIE-ID-246-not-to-be-used					ProtocolIE-ID ::= 246
id-ProtocolIE-ID-247-not-to-be-used					ProtocolIE-ID ::= 247
id-AdditionalRRMPriorityIndex						ProtocolIE-ID ::= 248
id-DUCURadioInformationType							ProtocolIE-ID ::= 249
id-CUDURadioInformationType 						ProtocolIE-ID ::= 250
id-AggressorgNBSetID								ProtocolIE-ID ::= 251
id-VictimgNBSetID									ProtocolIE-ID ::= 252
id-LowerLayerPresenceStatusChange					ProtocolIE-ID ::= 253
id-Transport-Layer-Address-Info						ProtocolIE-ID ::= 254
id-Neighbour-Cell-Information-Item					ProtocolIE-ID ::= 255
id-IntendedTDD-DL-ULConfig							ProtocolIE-ID ::= 256
id-QosMonitoringRequest								ProtocolIE-ID ::= 257
id-BHChannels-ToBeSetup-List						ProtocolIE-ID ::= 258
id-BHChannels-ToBeSetup-Item						ProtocolIE-ID ::= 259
id-BHChannels-Setup-List							ProtocolIE-ID ::= 260
id-BHChannels-Setup-Item							ProtocolIE-ID ::= 261
id-BHChannels-ToBeModified-Item						ProtocolIE-ID ::= 262
id-BHChannels-ToBeModified-List						ProtocolIE-ID ::= 263
id-BHChannels-ToBeReleased-Item						ProtocolIE-ID ::= 264
id-BHChannels-ToBeReleased-List						ProtocolIE-ID ::= 265
id-BHChannels-ToBeSetupMod-Item						ProtocolIE-ID ::= 266
id-BHChannels-ToBeSetupMod-List						ProtocolIE-ID ::= 267
id-BHChannels-FailedToBeModified-Item				ProtocolIE-ID ::= 268
id-BHChannels-FailedToBeModified-List				ProtocolIE-ID ::= 269
id-BHChannels-FailedToBeSetupMod-Item				ProtocolIE-ID ::= 270
id-BHChannels-FailedToBeSetupMod-List				ProtocolIE-ID ::= 271
id-BHChannels-Modified-Item							ProtocolIE-ID ::= 272
id-BHChannels-Modified-List							ProtocolIE-ID ::= 273
id-BHChannels-SetupMod-Item							ProtocolIE-ID ::= 274
id-BHChannels-SetupMod-List							ProtocolIE-ID ::= 275
id-BHChannels-Required-ToBeReleased-Item			ProtocolIE-ID ::= 276
id-BHChannels-Required-ToBeReleased-List			ProtocolIE-ID ::= 277
id-BHChannels-FailedToBeSetup-Item					ProtocolIE-ID ::= 278
id-BHChannels-FailedToBeSetup-List					ProtocolIE-ID ::= 279
id-BHInfo											ProtocolIE-ID ::= 280
id-BAPAddress										ProtocolIE-ID ::= 281
id-ConfiguredBAPAddress								ProtocolIE-ID ::= 282
id-BH-Routing-Information-Added-List				ProtocolIE-ID ::= 283
id-BH-Routing-Information-Added-List-Item			ProtocolIE-ID ::= 284
id-BH-Routing-Information-Removed-List				ProtocolIE-ID ::= 285
id-BH-Routing-Information-Removed-List-Item			ProtocolIE-ID ::= 286
id-UL-BH-Non-UP-Traffic-Mapping						ProtocolIE-ID ::= 287
id-Activated-Cells-to-be-Updated-List				ProtocolIE-ID ::= 288
id-Child-Nodes-List									ProtocolIE-ID ::= 289
id-IAB-Info-IAB-DU									ProtocolIE-ID ::= 290
id-IAB-Info-IAB-donor-CU							ProtocolIE-ID ::= 291
id-IAB-TNL-Addresses-To-Remove-List					ProtocolIE-ID ::= 292
id-IAB-TNL-Addresses-To-Remove-Item					ProtocolIE-ID ::= 293
id-IAB-Allocated-TNL-Address-List					ProtocolIE-ID ::= 294
id-IAB-Allocated-TNL-Address-Item					ProtocolIE-ID ::= 295
id-IABIPv6RequestType								ProtocolIE-ID ::= 296
id-IABv4AddressesRequested							ProtocolIE-ID ::= 297
id-IAB-Barred										ProtocolIE-ID ::= 298
id-TrafficMappingInformation						ProtocolIE-ID ::= 299
id-UL-UP-TNL-Information-to-Update-List				ProtocolIE-ID ::= 300
id-UL-UP-TNL-Information-to-Update-List-Item		ProtocolIE-ID ::= 301
id-UL-UP-TNL-Address-to-Update-List					ProtocolIE-ID ::= 302
id-UL-UP-TNL-Address-to-Update-List-Item			ProtocolIE-ID ::= 303
id-DL-UP-TNL-Address-to-Update-List					ProtocolIE-ID ::= 304
id-DL-UP-TNL-Address-to-Update-List-Item			ProtocolIE-ID ::= 305
id-NRV2XServicesAuthorized							ProtocolIE-ID ::= 306
id-LTEV2XServicesAuthorized							ProtocolIE-ID ::= 307
id-NRUESidelinkAggregateMaximumBitrate				ProtocolIE-ID ::= 308
id-LTEUESidelinkAggregateMaximumBitrate				ProtocolIE-ID ::= 309
id-SIB12-message									ProtocolIE-ID ::= 310
id-SIB13-message									ProtocolIE-ID ::= 311
id-SIB14-message									ProtocolIE-ID ::= 312
id-SLDRBs-FailedToBeModified-Item					ProtocolIE-ID ::= 313
id-SLDRBs-FailedToBeModified-List					ProtocolIE-ID ::= 314
id-SLDRBs-FailedToBeSetup-Item						ProtocolIE-ID ::= 315
id-SLDRBs-FailedToBeSetup-List						ProtocolIE-ID ::= 316
id-SLDRBs-Modified-Item								ProtocolIE-ID ::= 317
id-SLDRBs-Modified-List								ProtocolIE-ID ::= 318
id-SLDRBs-Required-ToBeModified-Item				ProtocolIE-ID ::= 319
id-SLDRBs-Required-ToBeModified-List				ProtocolIE-ID ::= 320
id-SLDRBs-Required-ToBeReleased-Item				ProtocolIE-ID ::= 321
id-SLDRBs-Required-ToBeReleased-List				ProtocolIE-ID ::= 322
id-SLDRBs-Setup-Item								ProtocolIE-ID ::= 323
id-SLDRBs-Setup-List								ProtocolIE-ID ::= 324
id-SLDRBs-ToBeModified-Item							ProtocolIE-ID ::= 325
id-SLDRBs-ToBeModified-List							ProtocolIE-ID ::= 326
id-SLDRBs-ToBeReleased-Item							ProtocolIE-ID ::= 327
id-SLDRBs-ToBeReleased-List							ProtocolIE-ID ::= 328
id-SLDRBs-ToBeSetup-Item							ProtocolIE-ID ::= 329
id-SLDRBs-ToBeSetup-List							ProtocolIE-ID ::= 330
id-SLDRBs-ToBeSetupMod-Item							ProtocolIE-ID ::= 331
id-SLDRBs-ToBeSetupMod-List							ProtocolIE-ID ::= 332
id-SLDRBs-SetupMod-List								ProtocolIE-ID ::= 333
id-SLDRBs-FailedToBeSetupMod-List					ProtocolIE-ID ::= 334
id-SLDRBs-SetupMod-Item								ProtocolIE-ID ::= 335
id-SLDRBs-FailedToBeSetupMod-Item					ProtocolIE-ID ::= 336
id-SLDRBs-ModifiedConf-List							ProtocolIE-ID ::= 337
id-SLDRBs-ModifiedConf-Item							ProtocolIE-ID ::= 338
id-UEAssistanceInformationEUTRA						ProtocolIE-ID ::= 339
id-PC5LinkAMBR										ProtocolIE-ID ::= 340
id-SL-PHY-MAC-RLC-Config							ProtocolIE-ID ::= 341
id-SL-ConfigDedicatedEUTRA-Info						ProtocolIE-ID ::= 342
id-AlternativeQoSParaSetList						ProtocolIE-ID ::= 343
id-CurrentQoSParaSetIndex							ProtocolIE-ID ::= 344
id-gNBCUMeasurementID								ProtocolIE-ID ::= 345
id-gNBDUMeasurementID								ProtocolIE-ID ::= 346
id-RegistrationRequest								ProtocolIE-ID ::= 347
id-ReportCharacteristics							ProtocolIE-ID ::= 348
id-CellToReportList									ProtocolIE-ID ::= 349
id-CellMeasurementResultList						ProtocolIE-ID ::= 350
id-HardwareLoadIndicator							ProtocolIE-ID ::= 351
id-ReportingPeriodicity								ProtocolIE-ID ::= 352
id-TNLCapacityIndicator								ProtocolIE-ID ::= 353
id-CarrierList										ProtocolIE-ID ::= 354
id-ULCarrierList									ProtocolIE-ID ::= 355
id-FrequencyShift7p5khz								ProtocolIE-ID ::= 356
id-SSB-PositionsInBurst								ProtocolIE-ID ::= 357
id-NRPRACHConfig									ProtocolIE-ID ::= 358
id-RAReportList										ProtocolIE-ID ::= 359
id-RLFReportInformationList							ProtocolIE-ID ::= 360
id-TDD-UL-DLConfigCommonNR							ProtocolIE-ID ::= 361
id-CNPacketDelayBudgetDownlink						ProtocolIE-ID ::= 362
id-ExtendedPacketDelayBudget						ProtocolIE-ID ::= 363
id-TSCTrafficCharacteristics						ProtocolIE-ID ::= 364
id-ReportingRequestType								ProtocolIE-ID ::= 365
id-TimeReferenceInformation							ProtocolIE-ID ::= 366
id-CNPacketDelayBudgetUplink						ProtocolIE-ID ::= 369
id-AdditionalPDCPDuplicationTNL-List				ProtocolIE-ID ::= 370
id-RLCDuplicationInformation						ProtocolIE-ID ::= 371
id-AdditionalDuplicationIndication					ProtocolIE-ID ::= 372
id-ConditionalInterDUMobilityInformation			ProtocolIE-ID ::= 373
id-ConditionalIntraDUMobilityInformation			ProtocolIE-ID ::= 374
id-targetCellsToCancel								ProtocolIE-ID ::= 375
id-requestedTargetCellGlobalID						ProtocolIE-ID ::= 376
id-ManagementBasedMDTPLMNList						ProtocolIE-ID ::= 377
id-TraceCollectionEntityIPAddress 					ProtocolIE-ID ::= 378
id-PrivacyIndicator									ProtocolIE-ID ::= 379
id-TraceCollectionEntityURI							ProtocolIE-ID ::= 380
id-mdtConfiguration									ProtocolIE-ID ::= 381
id-ServingNID										ProtocolIE-ID ::= 382
id-NPNBroadcastInformation							ProtocolIE-ID ::= 383
id-NPNSupportInfo									ProtocolIE-ID ::= 384
id-NID												ProtocolIE-ID ::= 385
id-AvailableSNPN-ID-List							ProtocolIE-ID ::= 386
id-SIB10-message									ProtocolIE-ID ::= 387
id-DLCarrierList									ProtocolIE-ID ::= 389
	id-ExtendedTAISliceSupportList					ProtocolIE-ID ::= 390
id-RequestedSRSTransmissionCharacteristics			ProtocolIE-ID ::= 391
id-PosAssistance-Information						ProtocolIE-ID ::= 392
id-PosBroadcast										ProtocolIE-ID ::= 393
id-RoutingID										ProtocolIE-ID ::= 394
id-PosAssistanceInformationFailureList				ProtocolIE-ID ::= 395
id-PosMeasurementQuantities							ProtocolIE-ID ::= 396
id-PosMeasurementResultList							ProtocolIE-ID ::= 397
id-TRPInformationTypeListTRPReq						ProtocolIE-ID ::= 398
id-TRPInformationTypeItem							ProtocolIE-ID ::= 399
id-TRPInformationListTRPResp						ProtocolIE-ID ::= 400
id-TRPInformationItem								ProtocolIE-ID ::= 401
id-LMF-MeasurementID								ProtocolIE-ID ::= 402
id-SRSType											ProtocolIE-ID ::= 403
id-ActivationTime									ProtocolIE-ID ::= 404
id-AbortTransmission								ProtocolIE-ID ::= 405
id-PositioningBroadcastCells						ProtocolIE-ID ::= 406
id-SRSConfiguration									ProtocolIE-ID ::= 407
id-PosReportCharacteristics							ProtocolIE-ID ::= 408
id-PosMeasurementPeriodicity						ProtocolIE-ID ::= 409
id-TRPList											ProtocolIE-ID ::= 410
id-RAN-MeasurementID								ProtocolIE-ID ::= 411
id-LMF-UE-MeasurementID								ProtocolIE-ID ::= 412
id-RAN-UE-MeasurementID								ProtocolIE-ID ::= 413
id-E-CID-MeasurementQuantities						ProtocolIE-ID ::= 414
id-E-CID-MeasurementQuantities-Item					ProtocolIE-ID ::= 415
id-E-CID-MeasurementPeriodicity						ProtocolIE-ID ::= 416
id-E-CID-MeasurementResult							ProtocolIE-ID ::= 417
id-Cell-Portion-ID									ProtocolIE-ID ::= 418
id-SFNInitialisationTime							ProtocolIE-ID ::= 419
id-SystemFrameNumber								ProtocolIE-ID ::= 420
id-SlotNumber										ProtocolIE-ID ::= 421
id-TRP-MeasurementRequestList						ProtocolIE-ID ::= 422
id-MeasurementBeamInfoRequest						ProtocolIE-ID ::= 423
id-E-CID-ReportCharacteristics						ProtocolIE-ID ::= 424
id-ConfiguredTACIndication							ProtocolIE-ID ::= 425
id-Extended-GNB-CU-Name								ProtocolIE-ID ::= 426
id-Extended-GNB-DU-Name								ProtocolIE-ID ::= 427
id-F1CTransferPath									ProtocolIE-ID ::= 428
id-SFN-Offset										ProtocolIE-ID ::= 429
id-TransmissionStopIndicator						ProtocolIE-ID ::= 430
id-SrsFrequency										ProtocolIE-ID ::= 431
id-SCGIndicator										ProtocolIE-ID ::= 432
id-EstimatedArrivalProbability						ProtocolIE-ID ::= 433
id-TRPType											ProtocolIE-ID ::= 434
id-SRSSpatialRelationPerSRSResource					ProtocolIE-ID ::= 435
id-PDCPTerminatingNodeDLTNLAddrInfo					ProtocolIE-ID ::= 436
id-ENBDLTNLAddress									ProtocolIE-ID ::= 437
id-PosMeasurementPeriodicityExtended				ProtocolIE-ID ::= 438
id-PRS-Resource-ID									ProtocolIE-ID ::= 439
id-LocationMeasurementInformation					ProtocolIE-ID ::= 440
id-SliceRadioResourceStatus							ProtocolIE-ID ::= 441
id-CompositeAvailableCapacity-SUL					ProtocolIE-ID ::= 442
id-SuccessfulHOReportInformationList				ProtocolIE-ID ::= 443
id-NR-U-Channel-List								ProtocolIE-ID ::= 444
id-NR-U												ProtocolIE-ID ::= 445
id-Coverage-Modification-Notification				ProtocolIE-ID ::= 446
id-CCO-Assistance-Information						ProtocolIE-ID ::= 447
id-ProtocolIE-ID-448-not-to-be-used				ProtocolIE-ID ::= 448
id-CellsForSON-List									ProtocolIE-ID ::= 449
id-MIMOPRBusageInformation							ProtocolIE-ID ::= 450
id-gNB-CU-MBS-F1AP-ID								ProtocolIE-ID ::= 451
id-gNB-DU-MBS-F1AP-ID								ProtocolIE-ID ::= 452
id-ProtocolIE-ID-453-not-to-be-used				ProtocolIE-ID ::= 453
id-MBS-CUtoDURRCInformation							ProtocolIE-ID ::= 454
id-MBS-Session-ID									ProtocolIE-ID ::= 455
id-SNSSAI											ProtocolIE-ID ::= 456
id-MBS-Broadcast-NeighbourCellList					ProtocolIE-ID ::= 457
id-BroadcastMRBs-FailedToBeModified-List			ProtocolIE-ID ::= 458
id-BroadcastMRBs-FailedToBeModified-Item			ProtocolIE-ID ::= 459
id-BroadcastMRBs-FailedToBeSetup-List				ProtocolIE-ID ::= 460
id-BroadcastMRBs-FailedToBeSetup-Item				ProtocolIE-ID ::= 461
id-BroadcastMRBs-FailedToBeSetupMod-List			ProtocolIE-ID ::= 462
id-BroadcastMRBs-FailedToBeSetupMod-Item			ProtocolIE-ID ::= 463
id-BroadcastMRBs-Modified-List						ProtocolIE-ID ::= 464
id-BroadcastMRBs-Modified-Item						ProtocolIE-ID ::= 465
id-BroadcastMRBs-Setup-List							ProtocolIE-ID ::= 466
id-BroadcastMRBs-Setup-Item							ProtocolIE-ID ::= 467
id-BroadcastMRBs-SetupMod-List						ProtocolIE-ID ::= 468
id-BroadcastMRBs-SetupMod-Item						ProtocolIE-ID ::= 469
id-BroadcastMRBs-ToBeModified-List					ProtocolIE-ID ::= 470
id-BroadcastMRBs-ToBeModified-Item					ProtocolIE-ID ::= 471
id-BroadcastMRBs-ToBeReleased-List					ProtocolIE-ID ::= 472
id-BroadcastMRBs-ToBeReleased-Item					ProtocolIE-ID ::= 473
id-BroadcastMRBs-ToBeSetup-List						ProtocolIE-ID ::= 474
id-BroadcastMRBs-ToBeSetup-Item						ProtocolIE-ID ::= 475
id-BroadcastMRBs-ToBeSetupMod-List					ProtocolIE-ID ::= 476
id-BroadcastMRBs-ToBeSetupMod-Item					ProtocolIE-ID ::= 477
id-Supported-MBS-FSA-ID-List						ProtocolIE-ID ::= 478
id-UEIdentity-List-For-Paging-List 					ProtocolIE-ID ::= 479
id-UEIdentity-List-For-Paging-Item 					ProtocolIE-ID ::= 480
id-MBS-ServiceArea									ProtocolIE-ID ::= 481
id-MulticastMRBs-FailedToBeModified-List			ProtocolIE-ID ::= 482
id-MulticastMRBs-FailedToBeModified-Item			ProtocolIE-ID ::= 483
id-MulticastMRBs-FailedToBeSetup-List				ProtocolIE-ID ::= 484
id-MulticastMRBs-FailedToBeSetup-Item				ProtocolIE-ID ::= 485
id-MulticastMRBs-FailedToBeSetupMod-List			ProtocolIE-ID ::= 486
id-MulticastMRBs-FailedToBeSetupMod-Item			ProtocolIE-ID ::= 487
id-MulticastMRBs-Modified-List						ProtocolIE-ID ::= 488
id-MulticastMRBs-Modified-Item						ProtocolIE-ID ::= 489
id-MulticastMRBs-Setup-List							ProtocolIE-ID ::= 490
id-MulticastMRBs-Setup-Item							ProtocolIE-ID ::= 491
id-MulticastMRBs-SetupMod-List						ProtocolIE-ID ::= 492
id-MulticastMRBs-SetupMod-Item						ProtocolIE-ID ::= 493
id-MulticastMRBs-ToBeModified-List					ProtocolIE-ID ::= 494
id-MulticastMRBs-ToBeModified-Item					ProtocolIE-ID ::= 495
id-MulticastMRBs-ToBeReleased-List					ProtocolIE-ID ::= 496
id-MulticastMRBs-ToBeReleased-Item					ProtocolIE-ID ::= 497
id-MulticastMRBs-ToBeSetup-List						ProtocolIE-ID ::= 498
id-MulticastMRBs-ToBeSetup-Item						ProtocolIE-ID ::= 499
id-MulticastMRBs-ToBeSetupMod-List					ProtocolIE-ID ::= 500
id-MulticastMRBs-ToBeSetupMod-Item					ProtocolIE-ID ::= 501
id-MBSMulticastF1UContextDescriptor					ProtocolIE-ID ::= 502
id-MulticastF1UContext-ToBeSetup-List				ProtocolIE-ID ::= 503
id-MulticastF1UContext-ToBeSetup-Item				ProtocolIE-ID ::= 504
id-MulticastF1UContext-Setup-List					ProtocolIE-ID ::= 505
id-MulticastF1UContext-Setup-Item					ProtocolIE-ID ::= 506
id-MulticastF1UContext-FailedToBeSetup-List			ProtocolIE-ID ::= 507
id-MulticastF1UContext-FailedToBeSetup-Item			ProtocolIE-ID ::= 508
id-IABCongestionIndication							ProtocolIE-ID ::= 509
id-IABConditionalRRCMessageDeliveryIndication		ProtocolIE-ID ::= 510
id-F1CTransferPathNRDC								ProtocolIE-ID ::= 511
id-BufferSizeThresh 								ProtocolIE-ID ::= 512
id-IAB-TNL-Addresses-Exception						ProtocolIE-ID ::= 513
id-BAP-Header-Rewriting-Added-List					ProtocolIE-ID ::= 514
id-BAP-Header-Rewriting-Added-List-Item				ProtocolIE-ID ::= 515
id-Re-routingEnableIndicator						ProtocolIE-ID ::= 516
id-NonF1terminatingTopologyIndicator				ProtocolIE-ID ::= 517
id-EgressNonF1terminatingTopologyIndicator			ProtocolIE-ID ::= 518
id-IngressNonF1terminatingTopologyIndicator			ProtocolIE-ID ::= 519
id-rBSetConfiguration 								ProtocolIE-ID ::= 520
id-frequency-Domain-HSNA-Configuration-List			ProtocolIE-ID ::= 521
id-child-IAB-Nodes-NA-Resource-List					ProtocolIE-ID ::= 522
id-Parent-IAB-Nodes-NA-Resource-Configuration-List	ProtocolIE-ID ::= 523
id-uL-FreqInfo										ProtocolIE-ID ::= 524
id-uL-Transmission-Bandwidth						ProtocolIE-ID ::= 525
id-dL-FreqInfo										ProtocolIE-ID ::= 526
id-dL-Transmission-Bandwidth						ProtocolIE-ID ::= 527
id-uL-NR-Carrier-List								ProtocolIE-ID ::= 528
id-dL-NR-Carrier-List								ProtocolIE-ID ::= 529
id-nRFreqInfo										ProtocolIE-ID ::= 530
id-transmission-Bandwidth							ProtocolIE-ID ::= 531
id-nR-Carrier-List									ProtocolIE-ID ::= 532
id-Neighbour-Node-Cells-List						ProtocolIE-ID ::= 533
id-Serving-Cells-List								ProtocolIE-ID ::= 534
id-permutation										ProtocolIE-ID ::= 535
id-MDTPollutedMeasurementIndicator					ProtocolIE-ID ::= 536
id-M5ReportAmount 									ProtocolIE-ID ::= 537
id-M6ReportAmount 									ProtocolIE-ID ::= 538
id-M7ReportAmount 									ProtocolIE-ID ::= 539
id-SurvivalTime										ProtocolIE-ID ::= 540
id-PDCMeasurementPeriodicity						ProtocolIE-ID ::= 541
id-PDCMeasurementQuantities							ProtocolIE-ID ::= 542
id-PDCMeasurementQuantities-Item					ProtocolIE-ID ::= 543
id-PDCMeasurementResult								ProtocolIE-ID ::= 544
id-PDCReportType									ProtocolIE-ID ::= 545
id-RAN-UE-PDC-MeasID								ProtocolIE-ID ::= 546
id-SCGActivationRequest								ProtocolIE-ID ::= 547
id-SCGActivationStatus								ProtocolIE-ID ::= 548
id-PRSTRPList										ProtocolIE-ID ::= 549
id-PRSTransmissionTRPList							ProtocolIE-ID ::= 550
id-OnDemandPRS										ProtocolIE-ID ::= 551
id-AoA-SearchWindow									ProtocolIE-ID ::= 552
id-TRP-MeasurementUpdateList						ProtocolIE-ID ::= 553
id-ZoAInformation									ProtocolIE-ID ::= 554
id-ResponseTime										ProtocolIE-ID ::= 555
id-ARPLocationInfo									ProtocolIE-ID ::= 556
id-ARP-ID											ProtocolIE-ID ::= 557
id-MultipleULAoA									ProtocolIE-ID ::= 558
id-UL-SRS-RSRPP										ProtocolIE-ID ::= 559
id-SRSResourcetype									ProtocolIE-ID ::= 560
id-ExtendedAdditionalPathList						ProtocolIE-ID ::= 561
id-LoS-NLoSInformation								ProtocolIE-ID ::= 562
id-NumberOfTRPRxTEG									ProtocolIE-ID ::= 564
id-NumberOfTRPRxTxTEG								ProtocolIE-ID ::= 565
id-TRPTxTEGAssociation								ProtocolIE-ID ::= 566
id-TRPTEGInformation								ProtocolIE-ID ::= 567
id-TRPRx-TEGInformation								ProtocolIE-ID ::= 568
id-TRP-PRS-Info-List								ProtocolIE-ID ::= 569
id-PRS-Measurement-Info-List						ProtocolIE-ID ::= 570
id-PRSConfigRequestType								ProtocolIE-ID ::= 571
id-MeasurementTimeOccasion							ProtocolIE-ID ::= 573
id-MeasurementCharacteristicsRequestIndicator		ProtocolIE-ID ::= 574
id-UEReportingInformation							ProtocolIE-ID ::= 575
id-PosContextRevIndication							ProtocolIE-ID ::= 576
id-TRPBeamAntennaInformation						ProtocolIE-ID ::= 577
id-NRRedCapUEIndication 							ProtocolIE-ID ::= 578
id-Redcap-Bcast-Information							ProtocolIE-ID ::= 579
id-RANUEPagingDRX									ProtocolIE-ID ::= 580
id-CNUEPagingDRX									ProtocolIE-ID ::= 581
id-NRPagingeDRXInformation							ProtocolIE-ID ::= 582
id-NRPagingeDRXInformationforRRCINACTIVE			ProtocolIE-ID ::= 583
id-NR-TADV											ProtocolIE-ID ::= 584
id-QoEInformation									ProtocolIE-ID ::= 585
id-CG-SDTQueryIndication							ProtocolIE-ID ::= 586
id-SDT-MAC-PHY-CG-Config							ProtocolIE-ID ::= 587
id-CG-SDTKeptIndicator								ProtocolIE-ID ::= 588
id-CG-SDTindicatorSetup								ProtocolIE-ID ::= 589
id-CG-SDTindicatorMod								ProtocolIE-ID ::= 590
id-CG-SDTSessionInfoOld								ProtocolIE-ID ::= 591
id-SDTInformation									ProtocolIE-ID ::= 592
id-SDTRLCBearerConfiguration						ProtocolIE-ID ::= 593
id-FiveG-ProSeAuthorized							ProtocolIE-ID ::= 594
id-FiveG-ProSeUEPC5AggregateMaximumBitrate			ProtocolIE-ID ::= 595
id-FiveG-ProSePC5LinkAMBR	 						ProtocolIE-ID ::= 596
id-SRBMappingInfo									ProtocolIE-ID ::= 597
id-DRBMappingInfo									ProtocolIE-ID ::= 598
id-UuRLCChannelToBeSetupList						ProtocolIE-ID ::= 599
id-UuRLCChannelToBeModifiedList						ProtocolIE-ID ::= 600
id-UuRLCChannelToBeReleasedList						ProtocolIE-ID ::= 601
id-UuRLCChannelSetupList							ProtocolIE-ID ::= 602
id-UuRLCChannelFailedToBeSetupList					ProtocolIE-ID ::= 603
id-UuRLCChannelModifiedList							ProtocolIE-ID ::= 604
id-UuRLCChannelFailedToBeModifiedList				ProtocolIE-ID ::= 605
id-UuRLCChannelRequiredToBeModifiedList				ProtocolIE-ID ::= 606
id-UuRLCChannelRequiredToBeReleasedList				ProtocolIE-ID ::= 607
id-PC5RLCChannelToBeSetupList						ProtocolIE-ID ::= 608
id-PC5RLCChannelToBeModifiedList					ProtocolIE-ID ::= 609
id-PC5RLCChannelToBeReleasedList					ProtocolIE-ID ::= 610
id-PC5RLCChannelSetupList							ProtocolIE-ID ::= 611
id-PC5RLCChannelFailedToBeSetupList					ProtocolIE-ID ::= 612
id-PC5RLCChannelFailedToBeModifiedList				ProtocolIE-ID ::= 613
id-PC5RLCChannelRequiredToBeModifiedList			ProtocolIE-ID ::= 614
id-PC5RLCChannelRequiredToBeReleasedList			ProtocolIE-ID ::= 615
id-PC5RLCChannelModifiedList						ProtocolIE-ID ::= 616
id-SidelinkRelayConfiguration						ProtocolIE-ID ::= 617
id-UpdatedRemoteUELocalID							ProtocolIE-ID ::= 618
id-PathSwitchConfiguration							ProtocolIE-ID ::= 619
id-PagingCause										ProtocolIE-ID ::= 620
id-MUSIM-GapConfig									ProtocolIE-ID ::= 621
id-PEIPSAssistanceInfo								ProtocolIE-ID ::= 622
id-UEPagingCapability								ProtocolIE-ID ::= 623
id-LastUsedCellIndication							ProtocolIE-ID ::= 624
id-SIB17-message									ProtocolIE-ID ::= 625
id-GNBDUUESliceMaximumBitRateList					ProtocolIE-ID ::= 626
id-SIB20-message									ProtocolIE-ID ::= 627
id-UE-MulticastMRBs-ToBeReleased-List				ProtocolIE-ID ::= 628
id-UE-MulticastMRBs-ToBeReleased-Item				ProtocolIE-ID ::= 629
id-UE-MulticastMRBs-ToBeSetup-List					ProtocolIE-ID ::= 630
id-UE-MulticastMRBs-ToBeSetup-Item					ProtocolIE-ID ::= 631
id-MulticastMBSSessionSetupList						ProtocolIE-ID ::= 632
id-MulticastMBSSessionRemoveList					ProtocolIE-ID ::= 633
id-PosMeasurementAmount								ProtocolIE-ID ::= 634
id-SDT-Termination-Request							ProtocolIE-ID ::= 635
id-pathPower										ProtocolIE-ID ::= 636
id-DU-RX-MT-RX-Extend								ProtocolIE-ID ::= 637
id-DU-TX-MT-TX-Extend								ProtocolIE-ID ::= 638
id-DU-RX-MT-TX-Extend								ProtocolIE-ID ::= 639
id-DU-TX-MT-RX-Extend								ProtocolIE-ID ::= 640
id-BAP-Header-Rewriting-Removed-List				ProtocolIE-ID ::= 641
id-BAP-Header-Rewriting-Removed-List-Item			ProtocolIE-ID ::= 642
id-SLDRXCycleList									ProtocolIE-ID ::= 643
id-TAINSAGSupportList								ProtocolIE-ID ::= 644
id-SL-RLC-ChannelToAddModList						ProtocolIE-ID ::= 645
id-BroadcastAreaScope								ProtocolIE-ID ::= 646
id-ManagementBasedMDTPLMNModificationList 			ProtocolIE-ID ::= 647
id-SIB15-message									ProtocolIE-ID ::= 648
id-ActivationRequestType							ProtocolIE-ID ::= 649
id-PosMeasGapPreConfigList							ProtocolIE-ID ::= 650
id-InterFrequencyConfig-NoGap						ProtocolIE-ID ::= 651
id-MBSInterestIndication							ProtocolIE-ID ::= 652
id-UE-MulticastMRBs-ConfirmedToBeModified-List		ProtocolIE-ID ::= 653
id-UE-MulticastMRBs-ConfirmedToBeModified-Item		ProtocolIE-ID ::= 654
id-UE-MulticastMRBs-RequiredToBeModified-List		ProtocolIE-ID ::= 655
id-UE-MulticastMRBs-RequiredToBeModified-Item		ProtocolIE-ID ::= 656
id-UE-MulticastMRBs-RequiredToBeReleased-List		ProtocolIE-ID ::= 657
id-UE-MulticastMRBs-RequiredToBeReleased-Item		ProtocolIE-ID ::= 658
id-L571Info											ProtocolIE-ID ::= 659
id-L1151Info										ProtocolIE-ID ::= 660
id-SCS-480											ProtocolIE-ID ::= 661
id-SCS-960											ProtocolIE-ID ::= 662
id-SRSPortIndex										ProtocolIE-ID ::= 663
id-PEISubgroupingSupportIndication					ProtocolIE-ID ::= 664
id-NeedForGapsInfoNR								ProtocolIE-ID ::= 665
id-NeedForGapNCSGInfoNR								ProtocolIE-ID ::= 666
id-NeedForGapNCSGInfoEUTRA							ProtocolIE-ID ::= 667
id-ProtocolIE-ID-668-not-to-be-used				ProtocolIE-ID ::= 668
id-ProtocolIE-ID-669-not-to-be-used				ProtocolIE-ID ::= 669
id-ProtocolIE-ID-670-not-to-be-used				ProtocolIE-ID ::= 670
id-Source-MRB-ID									ProtocolIE-ID ::= 671
id-PosMeasurementPeriodicityNR-AoA					ProtocolIE-ID ::= 672
id-RedCapIndication									ProtocolIE-ID ::= 673
id-SRSPosRRCInactiveConfig							ProtocolIE-ID ::= 674
id-SDTBearerConfigurationQueryIndication			ProtocolIE-ID ::= 675
id-SDTBearerConfigurationInfo						ProtocolIE-ID ::= 676
id-UL-GapFR2-Config									ProtocolIE-ID ::= 677
id-ConfigRestrictInfoDAPS							ProtocolIE-ID ::= 678
id-UE-MulticastMRBs-Setup-List						ProtocolIE-ID ::= 679
id-UE-MulticastMRBs-Setup-Item						ProtocolIE-ID ::= 680
id-MulticastF1UContextReferenceCU					ProtocolIE-ID ::= 681
id-PosSItypeList									ProtocolIE-ID ::= 682
id-DAPS-HO-Status									ProtocolIE-ID ::= 683
id-UplinkTxDirectCurrentTwoCarrierListInfo			ProtocolIE-ID ::= 684
id-UE-MulticastMRBs-ToBeSetup-atModify-List			ProtocolIE-ID ::= 685
id-UE-MulticastMRBs-ToBeSetup-atModify-Item			ProtocolIE-ID ::= 686
id-MC-PagingCell-List								ProtocolIE-ID ::= 687
id-MC-PagingCell-Item								ProtocolIE-ID ::= 688
id-SRSPosRRCInactiveQueryIndication					ProtocolIE-ID ::= 689
id-UlTxDirectCurrentMoreCarrierInformation	        ProtocolIE-ID ::= 690
id-CPACMCGInformation								ProtocolIE-ID ::= 691
id-TwoPHRModeMCG									ProtocolIE-ID ::= 692
id-TwoPHRModeSCG									ProtocolIE-ID ::= 693
id-ExtendedUEIdentityIndexValue						ProtocolIE-ID ::= 694
id-ServingCellMO-List								ProtocolIE-ID ::= 695
id-ServingCellMO-List-Item							ProtocolIE-ID ::= 696
id-ServingCellMO-encoded-in-CGC-List				ProtocolIE-ID ::= 697
id-HashedUEIdentityIndexValue						ProtocolIE-ID ::= 698
id-UE-MulticastMRBs-Setupnew-List					ProtocolIE-ID ::= 699
id-UE-MulticastMRBs-Setupnew-Item					ProtocolIE-ID ::= 700
id-ncd-SSB-RedCapInitialBWP-SDT						ProtocolIE-ID ::= 701
id-nrofSymbolsExtended								ProtocolIE-ID ::= 702
id-repetitionFactorExtended							ProtocolIE-ID ::= 703
id-startRBHopping									ProtocolIE-ID ::= 704
id-startRBIndex										ProtocolIE-ID ::= 705
id-transmissionCombn8								ProtocolIE-ID ::= 706
id-ServCellInfoList									ProtocolIE-ID ::= 707
id-DedicatedSIDeliveryIndication					ProtocolIE-ID ::= 708
id-Configured-BWP-List								ProtocolIE-ID ::= 709
id-Preconfigured-measurement-GAP-Request			ProtocolIE-ID ::= 710
id-BWP-Id											ProtocolIE-ID ::= 711
id-NetworkControlledRepeaterAuthorized				ProtocolIE-ID ::= 712
id-MT-SDT-Information								ProtocolIE-ID ::= 713
id-ExtendedResourceSymbolOffset						ProtocolIE-ID ::= 714
id-NeedForInterruptionInfoNR						ProtocolIE-ID ::= 715
id-SDT-Volume-Threshold								ProtocolIE-ID ::= 716
id-SupportedUETypeList								ProtocolIE-ID ::= 717
id-MusimCapabilityRestrictionIndication				ProtocolIE-ID ::= 718
id-duplicationIndication							ProtocolIE-ID ::= 719
id-LTMInformation-Setup								ProtocolIE-ID ::= 720
id-LTMConfigurationIDMappingList 					ProtocolIE-ID ::= 721
id-LTMInformation-Modify							ProtocolIE-ID ::= 722
id-LTMCells-ToBeReleased-List						ProtocolIE-ID ::= 723
id-ProtocolIE-ID-724-not-to-be-used						ProtocolIE-ID ::= 724
id-LTMConfiguration									ProtocolIE-ID ::= 725
id-EarlySyncInformation-Request						ProtocolIE-ID ::= 726
id-EarlySyncInformation								ProtocolIE-ID ::= 727
id-EarlySyncCandidateCellInformation-List			ProtocolIE-ID ::= 728
id-LTMCellSwitchInformation							ProtocolIE-ID ::= 729
id-DUtoCUTAInformation-List							ProtocolIE-ID ::= 730
id-ProtocolIE-ID-731-not-to-be-used					ProtocolIE-ID ::= 731
id-dRB-List											ProtocolIE-ID ::= 732
id-DeactivationIndication							ProtocolIE-ID ::= 733
id-RAReportIndicationList							ProtocolIE-ID ::= 734
id-ChannelOccupancyTimePercentageUL					ProtocolIE-ID ::= 735
id-SuccessfulPSCellChangeReportInformationList		ProtocolIE-ID ::= 736
id-RadioResourceStatusNR-U							ProtocolIE-ID ::= 737
id-FiveG-ProSeLayer2Multipath						ProtocolIE-ID ::= 738
id-FiveG-ProSeLayer2UEtoUERelay						ProtocolIE-ID ::= 739
id-FiveG-ProSeLayer2UEtoUERemote					ProtocolIE-ID ::= 740
id-PathAdditionInformation							ProtocolIE-ID ::= 741
id-Recommended-SSBs-List							ProtocolIE-ID ::= 742
id-Recommended-SSBs-for-Paging-List					ProtocolIE-ID ::= 743
id-SSBs-withinTheCell-tobe-Activated-List			ProtocolIE-ID ::= 744
id-Cells-With-SSBs-Activated-List					ProtocolIE-ID ::= 745
id-Cells-Allowed-to-be-Deactivated-List				ProtocolIE-ID ::= 746
id-Cells-Allowed-to-be-Deactivated-List-Item		ProtocolIE-ID ::= 747
id-Coverage-Modification-Cause						ProtocolIE-ID ::= 748
id-RANTSSRequestType								ProtocolIE-ID ::= 749
id-RANTimingSynchronisationStatusInfo				ProtocolIE-ID ::= 750
id-TSCTrafficCharacteristicsFeedback				ProtocolIE-ID ::= 751
id-RANfeedbacktype									ProtocolIE-ID ::= 752
id-Mobile-TRP-LocationInformation					ProtocolIE-ID ::= 753
id-Mobile-IAB-MT-UE-ID								ProtocolIE-ID ::= 754
id-Target-gNB-ID									ProtocolIE-ID ::= 755
id-Target-gNB-IP-address							ProtocolIE-ID ::= 756
id-Target-SeGW-IP-address							ProtocolIE-ID ::= 757
id-Activated-Cells-Mapping-List						ProtocolIE-ID ::= 758
id-Activated-Cells-Mapping-List-Item				ProtocolIE-ID ::= 759
id-F1SetupOutcome									ProtocolIE-ID ::= 760
id-RRC-Terminating-IAB-Donor-Related-Info			ProtocolIE-ID ::= 761
id-RRC-Terminating-IAB-Donor-gNB-ID					ProtocolIE-ID ::= 762
id-NCGI-to-be-Updated-List							ProtocolIE-ID ::= 763
id-NCGI-to-be-Updated-List-Item						ProtocolIE-ID ::= 764
id-Mobile-IAB-MTUserLocationInformation				ProtocolIE-ID ::= 765
id-MobileAccessPointLocation						ProtocolIE-ID ::= 766
id-AssociatedSessionID								ProtocolIE-ID ::= 767
id-IndicationMCInactiveReception					ProtocolIE-ID ::= 768
id-MulticastCU2DURRCInfo							ProtocolIE-ID ::= 769
id-MBSMulticastSessionReceptionState				ProtocolIE-ID ::= 770
id-F1UTunnelNotEstablished							ProtocolIE-ID ::= 771
id-MulticastDU2CURRCInfo							ProtocolIE-ID ::= 772
id-SIB24-message										ProtocolIE-ID ::= 773
id-MulticastCU2DUCommonRRCInfo						ProtocolIE-ID ::= 774
id-PDUSetQoSParameters								ProtocolIE-ID ::= 775
id-N6JitterInformation								ProtocolIE-ID ::= 776
id-ECNMarkingorCongestionInformationReportingRequest	ProtocolIE-ID ::= 777
id-ECNMarkingorCongestionInformationReportingStatus	ProtocolIE-ID ::= 778
id-NRA2XServicesAuthorized							ProtocolIE-ID ::= 779
id-LTEA2XServicesAuthorized							ProtocolIE-ID ::= 780
id-NRUESidelinkAggregateMaximumBitrateForA2X		ProtocolIE-ID ::= 781
id-LTEUESidelinkAggregateMaximumBitrateForA2X		ProtocolIE-ID ::= 782
id-NReRedCapUEIndication 							ProtocolIE-ID ::= 783
id-ERedcap-Bcast-Information 						ProtocolIE-ID ::= 784
id-NRPaginglongeDRXInformationforRRCINACTIVE		ProtocolIE-ID ::= 785
id-SCPAC-Request									ProtocolIE-ID ::= 786
id-Target-F1-Terminating-Donor-gNB-ID				ProtocolIE-ID ::= 787
id-MobileIAB-Barred									ProtocolIE-ID ::= 788
id-Broadcast-MRBs-Transport-Request-List 			ProtocolIE-ID ::= 789
id-Broadcast-MRBs-Transport-Request-Item			ProtocolIE-ID ::= 790
id-S-CPACLowerLayerReferenceConfigRequest			ProtocolIE-ID ::= 791
id-S-CPAC-Configuration								ProtocolIE-ID ::= 792
id-MusimCandidateBandList							ProtocolIE-ID ::= 793
id-DLLBTFailureInformationRequest					ProtocolIE-ID ::= 794
id-DLLBTFailureInformationList						ProtocolIE-ID ::= 795
id-PSIbasedSDUdiscardUL								ProtocolIE-ID ::= 796
id-SIB22-message 									ProtocolIE-ID ::= 797
id-CUtoDUTAInformation-List							ProtocolIE-ID ::= 798
id-U2URLCChannelQoS								ProtocolIE-ID ::= 799
id-SL-PHY-MAC-RLC-ConfigExt							ProtocolIE-ID ::= 800
id-SLPositioning-Ranging-Service-Info				ProtocolIE-ID ::= 801
id-TimeWindowInformation-SRS-List					ProtocolIE-ID ::= 802
id-TimeWindowInformation-Measurement-List			ProtocolIE-ID ::= 803
id-UL-RSCP											ProtocolIE-ID ::= 804
id-BW-Aggregation-Request-Indication				ProtocolIE-ID ::= 805
id-ReportingGranularitykminus1						ProtocolIE-ID ::= 806
id-ReportingGranularitykminus2						ProtocolIE-ID ::= 807
id-ReportingGranularitykminus1additionalpath		ProtocolIE-ID ::= 808
id-ReportingGranularitykminus2additionalpath		ProtocolIE-ID ::= 809
id-TimingReportingGranularityFactorExtended			ProtocolIE-ID ::= 810
id-SRSPosRRCInactiveValidityAreaConfig				ProtocolIE-ID ::= 811
id-PosValidityAreaCellList							ProtocolIE-ID ::= 812
id-SRSReservationType								ProtocolIE-ID ::= 813
id-SymbolIndex										ProtocolIE-ID ::= 814
id-PRSBWAggregationRequestInfoList					ProtocolIE-ID ::= 815
id-AggregatedPosSRSResourceIDList					ProtocolIE-ID ::= 816
id-AggregatedPRSResourceSetList						ProtocolIE-ID ::= 817
id-PhaseQuality										ProtocolIE-ID ::= 818
id-MeasuredFrequencyHops							ProtocolIE-ID ::= 819
id-TxHoppingConfiguration							ProtocolIE-ID ::= 820
id-ReportingGranularitykminus3						ProtocolIE-ID ::= 821
id-ReportingGranularitykminus4						ProtocolIE-ID ::= 822
id-ReportingGranularitykminus5						ProtocolIE-ID ::= 823
id-ReportingGranularitykminus6						ProtocolIE-ID ::= 824
id-ReportingGranularitykminus3additionalpath		ProtocolIE-ID ::= 825
id-ReportingGranularitykminus4additionalpath		ProtocolIE-ID ::= 826
id-ReportingGranularitykminus5additionalpath		ProtocolIE-ID ::= 827
id-ReportingGranularitykminus6additionalpath		ProtocolIE-ID ::= 828
id-AggregatedPosSRSResourceSetList					ProtocolIE-ID ::= 829
id-RequestedSRSPreconfigurationCharacteristics-List	ProtocolIE-ID ::= 830
id-SRSPreconfiguration-List							ProtocolIE-ID ::= 831
id-SRSInformation									ProtocolIE-ID ::= 832
id-ValidityAreaSpecificSRSInformation				ProtocolIE-ID ::= 833
id-E-CID-MeasuredResultsAssociatedInfoList			ProtocolIE-ID ::= 834
id-XR-Bcast-Information								ProtocolIE-ID ::= 835
id-MaxDataBurstVolume 								ProtocolIE-ID ::= 836
id-TAInformation-List								ProtocolIE-ID ::= 837
id-NonIntegerDRXCycle								ProtocolIE-ID ::= 838
id-PointA											ProtocolIE-ID ::= 839
id-SCS-SpecificCarrier								ProtocolIE-ID ::= 840
id-NR-PCI											ProtocolIE-ID ::= 841
id-PeerUE-ID											ProtocolIE-ID ::= 842
id-EarlySyncServingCellInformation					ProtocolIE-ID ::= 843
id-RANSharingAssistanceInformation					ProtocolIE-ID ::= 844
id-LTMCFRAResourceConfig-List						ProtocolIE-ID ::= 845
id-F1U-PathFailure									ProtocolIE-ID ::= 846
id-MeasBasedOnAggregatedResources					ProtocolIE-ID ::= 847
id-SIB23-message									ProtocolIE-ID ::= 848
id-BarringExemptionforEmerCallInfo					ProtocolIE-ID ::= 849
id-SIB17bis-message									ProtocolIE-ID ::= 850
id-ReportingIntervalIMs								ProtocolIE-ID ::= 851
id-Transmission-Bandwidth-asymmetric				ProtocolIE-ID ::= 852
id-TagIDPointer										ProtocolIE-ID ::= 853
id-LocalOrigin										ProtocolIE-ID ::= 854
id-LTMResetInformation								ProtocolIE-ID ::= 855
id-SRSPosPeriodicConfigHyperSFNIndex				ProtocolIE-ID ::= 856
id-PreconfiguredSRSInformation						ProtocolIE-ID ::= 857



END
